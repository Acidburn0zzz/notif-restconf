module ietf-http-subscribed-notifications {
  yang-version 1.1;
  namespace 
    "urn:ietf:params:xml:ns:yang:ietf-http-subscribed-notifications";

  prefix hsn;

  import ietf-subscribed-notifications {
    prefix sn;
  }
  import ietf-inet-types {
    prefix inet;
  }
  
  organization "IETF NETCONF (Network Configuration) Working Group";
  contact
    "WG Web:   <http:/tools.ietf.org/wg/netconf/>
     WG List:  <mailto:netconf@ietf.org>
          
     Editor:   Eric Voit
               <mailto:evoit@cisco.com>
     
     Editor:   Alexander Clemm
               <mailto:ludwig@clemm.org>
               
     Editor:   Reshad Rahman
               <mailto:rrahman@cisco.com>";

  description
    "Defines HTTP variants as a supported transports for subscribed
    event notifications.
    
    Copyright (c) 2018 IETF Trust and the persons identified as authors 
    of the code.  All rights reserved.

    Redistribution and use in source and binary forms, with or without 
    modification, is permitted pursuant to, and subject to the license 
    terms contained in, the Simplified BSD License set forth in Section 
    4.c of the IETF Trust's Legal Provisions Relating to IETF Documents
    (https://trustee.ietf.org/license-info).

    This version of this YANG module is part of RFC XXXX; see the RFC 
    itself for full legal notices.";
  
  revision 2018-06-11 {
    description
      "Initial version";
    reference 
      "RFC XXXX: RESTCONF and HTTP Transport for Event Notifications";
  }

  identity http2 {
    base sn:transport;
    base sn:inline-address;
	base sn:configurable-encoding;
    description
      "HTTP2 is used a transport for notification messages and state
       change notifications.";
  }

  identity http1.1 {
    base sn:transport;
    base sn:inline-address;
	base sn:configurable-encoding;
    description
      "HTTP1.1 is used a transport for notification messages and state
       change notifications.";
  }

  grouping uri {
    description
      "Provides a reusable description of a URI.";   
    leaf uri {
      type inet:uri;
      config false;
      description
        "Location of a subscription specific URI on the publisher.";
    }
  }
  
  augment "/sn:establish-subscription/sn:output" {
    description
      "This augmentation allows HTTP specific parameters for a 
      response to a publisher's subscription request.";
    uses uri;
  } 
  
  augment "/sn:subscriptions/sn:subscription" {
    description
      "This augmentation allows HTTP specific parameters to be
       exposed for a subscription.";
    uses uri;
  }

  augment "/sn:subscription-started" {
    description
      "This augmentation allows HTTP specific parameters to be included 
      part of the notification that a subscription has started.";
    uses uri;
  }  

  augment "/sn:subscription-modified" {
    description
      "This augmentation allows HTTP specific parameters to be included 
      part of the notification that a subscription has been modified.";
    uses uri;
  } 

}


  
  /*  Additional elements to include over time
  
  augment "/sn:subscriptions/sn:subscription" {
    when 'transport != "http2" and sn:configured-subscription-state';
    must 'sn:encoding = /configurable/encodings/http-configurable-encoding' {
      error-message "publisher doesn't support this encoding for an HTTP2 subscription";
    }
  }
    
*/
